FME workspace ReferencesData_Geojson.fmw

Parameters:
- SourceDataset_GEOJSON_31 = F:\temp06\OLD Version\Chantiers1030\References\URBIS\Reultats\URBIS_OSIRIS_StreetSurfaces_GroupStreet.geojson   # Source GeoJSON File or URL
- SourceDataset_GEOJSON_39 = F:\temp06\OLD Version\Chantiers1030\References\URBIS\Reultats\URBIS_OSIRIS_StreetSurfaces_IndexSurfaces.geojson   # Source GeoJSON File or URL
- SourceDataset_GEOJSON_10 = F:\temp06\OLD Version\Chantiers1030\References\URBIS\Reultats\URBIS_OSIRIS_StreetSurfaces_OnlyStreetSurfaces_SharedStreetNames.geojson   # Source GeoJSON File or URL
- SourceDataset_GEOJSON_13 = F:\temp06\OLD Version\Chantiers1030\References\URBIS\Reultats\URBIS_OSIRIS_StreetSurfaces_SharedStreetNodes.geojson   # Source GeoJSON File or URL
- SourceDataset_GEOJSON_12 = $(FME_MF_DIR)URBIS_OSIRIS_StreetSurfaces_GroupStreet_OnlyNodes.geojson   # Source GeoJSON File or URL
- SourceDataset_GEOJSON_8 = $(FME_MF_DIR)URBIS_OSIRIS_StreetSurfaces_GroupStreet.geojson   # Source GeoJSON File or URL
- SourceDataset_GEOJSON_7 = F:\temp06\OLD Version\Chantiers1030\References\URBIS\Reultats\URBIS_OSIRIS_StreetSurfaces_GroupNodes.geojson   # Source GeoJSON File or URL
- SourceDataset_GEOJSON = F:\temp06\OLD Version\Chantiers1030\References\URBIS\Reultats\URBIS_OSIRIS_StreetSurfaces_OnlyStreetSurfaces_Segments.geojson   # Source GeoJSON File or URL

Readers:
- GEOJSON_9: GEOJSON from $(SourceDataset_GEOJSON_31) in LL-WGS84
- GEOJSON_11: GEOJSON from $(SourceDataset_GEOJSON_39) in LL-WGS84
- GEOJSON_2: GEOJSON from $(SourceDataset_GEOJSON_10) in LL-WGS84
- GEOJSON_1: GEOJSON from $(SourceDataset_GEOJSON) in LL-WGS84
- GEOJSON_3: GEOJSON from $(SourceDataset_GEOJSON_13) in LL-WGS84
- GEOJSON_6: GEOJSON from $(SourceDataset_GEOJSON_12) in LL-WGS84
- GEOJSON_4: GEOJSON from $(SourceDataset_GEOJSON_8) in LL-WGS84
- GEOJSON_5: GEOJSON from $(SourceDataset_GEOJSON_7) in LL-WGS84

Note: Lista de calles con valores de referencia
URBIS_OSIRIS_Street (reader GEOJSON_9)
    attributes: id_street int, PW_NAME_FR string, PW_NAME_DU string, index_concatenated_surf string, StreetLength (m) float, Type string
Note: Lista de segmentos de calles
URBIS_OSIRIS_IndexSurfaces (reader GEOJSON_11)
    attributes: index int, id string, SSFT string, PW_NAME_FR string, PW_NAME_DU string

Bookmark: New Bookmark
URBIS_OSIRIS_StreetSurfaces (reader GEOJSON_1)
    attributes: id_street int, index_seg int, PW_NAME_FR string, PW_NAME_DU string, Type string, StreetLength (m) float
URBIS_OSIRIS_SharedStreetNodes (reader GEOJSON_3)
    attributes: id_nodes int, id_street_shared string, name_street_shared string, number_street_shared string
URBIS_OSIRIS_GroupStreet_OnlyNodes (reader GEOJSON_6)
    attributes: id_street int, PW_NAME_FR string, PW_NAME_DU string, id_street_shared string, name_street_shared string, id_nodes_shared string, number_nodes int

Bookmark: New Bookmark
URBIS_OSIRIS_Street (reader GEOJSON_4)
    attributes: id_street int, PW_NAME_FR string, PW_NAME_DU string, index_concatenated_surf string, StreetLength (m) float, Type string
URBIS_OSIRIS_Nodes (reader GEOJSON_5)
    attributes: id_nodes int, index_int int, name_street_int string, index_street_int string, Type string
